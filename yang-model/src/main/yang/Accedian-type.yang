module Accedian-type {
	yang-version 1.1;
	namespace "http://accedian.com/ns/yang/types";
	prefix acdt;
	
	organization
		"Accedian Networks Inc.";
	contact
		"Accedian Networks Inc.
		
		https://accedian.com/
		Email: info@accedian.com
		
		2351 Blvd Alfred-Nobel, Suite N-410
		Saint-Laurent (Montreal), Quebec,
		H4S 2A9, Canada
		
		Phone: +1.514.331.6181 or +1.866.685.8181";
	
	description
		"Accedian yang model common types.
		
		Copyright (c) Accedian Networks, Inc.
		All rights reserved";
	
	revision 2022-10-25 {
		description
			"Initial revision";
	}
	
	typedef id {
		type string;
		description
			"An identifier type. The format is application specific";
	}
	
	typedef error-tag {
		description
			"A tag specifying the error category";
		type string;
	}
	
	grouping error-data {
		container error {
			leaf tag {
				description
					"The category of the error";
				type error-tag;
			}
			leaf msg {
				type string;
				description
					"Human readable message describing the nature of the error reported in
					the state leaf. When no error is present (state != Error), this
					should read 'No error'";
			}
		}
	}
}
