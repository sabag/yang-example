module Accedian-service-endpoint {
	yang-version 1.1;
	namespace "http://accedian.com/ns/yang/service/endpoint";
	prefix acdsep;

	revision 2022-10-25 {
		description
			"Initial revision";
	}

	container service-endpoints {
		list service-endpoint {
			key endpoint-id;
			leaf endpoint-id {
				type string;
			}
			leaf endpoint-name {
				type string;
			}
			leaf description {
				type string;
			}
			leaf type {
				type string;
			}
		}
	}
}
