module Accedian-service-endpoint {
	yang-version 1.1;
	namespace "http://accedian.com/ns/yang/service/endpoint";
	prefix acdsep;
	
	import Accedian-type {
		prefix acdt;
	}
	
	import Accedian-service-endpoint-type {
		prefix acdsept;
	}
	
	import Accedian-session-type {
		prefix acdst;
	}
	
	import Accedian-extensions {
		prefix acdext;
	}
	
	organization
		"Accedian Networks Inc.";
	contact
		"Accedian Networks Inc.
		
		https://accedian.com/
		Email: info@accedian.com
		
		2351 Blvd Alfred-Nobel, Suite N-410
		Saint-Laurent (Montreal), Quebec,
		H4S 2A9, Canada
		
		Phone: +1.514.331.6181 or +1.866.685.8181";
	
	description
		"This module contains the definition of a Accedian service endpoint.
		
		Copyright (c) Accedian Networks, Inc.
		All rights reserved";
	
	revision 2022-10-25 {
		description
			"Initial revision";
	}
	
	notification state-change-event {
		description
			"This notification is sent when the state of the endpoint changes";
		
		leaf endpoint-id {
			description
				"An identifier specifying on which endpoint the state-change happened. This leaf
				will match the name of an existing endpoint-id";
			type string;
		}
		
		uses acdsept:service-endpoint-state-data;
	}
	
	container service-endpoints {
		list service-endpoint {
			description
				"The list of all service enpoints currently configured. Provides the config and state  of
				each service endpoint";
			key endpoint-id;
			
			leaf endpoint-id {
				type acdt:id;
				acdext:tag-metadata endpoint-id;
				description
					"The endpoint unique identifier.
					tag-metadata: This leaf will be included as part of the analytics
					metadata as { endpoint-id : <endpoint-id> }";
			}
			
			leaf endpoint-name {
				type string;
				acdext:tag-metadata endpoint-name;
				description
					"The name given to this service endpoint.
					tag-metadata: This leaf will be included as part of the analytics
					metadata as { endpoint-name : <endpoint-name> }";
			}
			
			leaf description {
				type string;
				description
					"A field that can be used to describe the endpoint role, location, etc...";
			}
			
			leaf type {
				type identityref {
					base acdsept:service-endpoint;
				}
				description
					"The type of service of this sessions";
			}
			
			container config {
				description
					"Endpoint specific configuration for this endpoint. The configuration is
					dependent on the service-endpoint type specified in endpoint-type.
					It is implemented as a Yang augment mount point";
			}
			
			container state {
				description
					"Defines the state information that can be retrieved for a service endpoint";
				config false;
				
				leaf version {
					type string;
					description
						"This leaf indicates the version of the service-endpoint.
						The format of the version is service endpoint specific";
				}
				
				leaf-list capabilities {
					type identityref {
						base acdst:session;
					}
					description
						"List of session types supported by the endpoint";
				}
				
				container status {
					uses acdsept:service-endpoint-state-data;
				}
			}
		}
	}
}
