module Accedian-service-endpoint-type {
	yang-version 1.1;
	namespace "http://accedian.com/ns/yang/service/endpoint/type";
	prefix acdsept;
	
	import Accedian-type {
		prefix acdt;
	}
	
	organization
		"Accedian Networks Inc.";
	contact
		"Accedian Networks Inc.
		
		https://accedian.com/
		Email: info@accedian.com
		
		2351 Blvd Alfred-Nobel, Suite N-410
		Saint-Laurent (Montreal), Quebec,
		H4S 2A9, Canada
		
		Phone: +1.514.331.6181 or +1.866.685.8181";
	
	description
		"This module contains the type definitions of a Accedian
		service endpoint.
		
		Copyright (c) Accedian Networks, Inc.
		All rights reserved";
	
	revision 2022-10-25 {
		description
			"Initial revision";
	}
	
	identity service-endpoint {
		description
			"Base type for the service endpoints";
	}
	
	identity ne-endpoint {
		base service-endpoint;
		description
			"This type correspond to a use case where
			the service endpoint is hosted on a NSO-L3VPN deployment";
	}
	
	identity agent-endpoint {
		base service-endpoint;
		description
			"This type correspond to a Sensor Orchestrator endpoint deployment";
	}
	
	identity so-endpoint {
		base service-endpoint;
		description
			"This type correspond to a Skylight Orchestrator endpoint `deployment";
	}
	
	typedef service-endpoint-status {
		description
			"Defines the different status that can apply to a service endpoint";
		
		type enumeration {
			enum "Ready" {
				description
					"The endpoint is configured and ready to perform actions such as
					starting a session";
			}
			
			enum "NotReady" {
				description
					"The service-endpoint is still in transition toward a Ready state. It is
					not in error but it cannot yet perform session actions";
			}
			
			enum "Error" {
				description
					"The service-endpoint is currently in error state. It cannot currently perform
					actions such as starting a session";
			}
		}
	}
	
	grouping service-endpoint-state-data {
		description
			"The data representing the current state of the session endpoint";
		
		leaf status {
			description
				"The current status of the endpoint. Each state is described in the type definition";
			type service-endpoint-status;
		}
		
		uses acdt:error-data {
			description
				"Present wen the status is in error. Not present otherwise";
		}
	}
}
