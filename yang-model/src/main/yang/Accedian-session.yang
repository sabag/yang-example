module Accedian-session {
	yang-version 1.1;
	namespace "http://accedian.com/ns/yang/session";
	prefix acdses;
	
	import Accedian-type {
		prefix acdt;
	}
	
	import Accedian-session-type {
		prefix acdst;
	}
	
	import Accedian-service-endpoint {
		prefix acdsep;
	}
	
	import Accedian-extensions {
		prefix acdext;
	}

	organization
		"Accedian Networks Inc.";
	contact
		"Accedian Networks Inc.
		
		https://accedian.com/
		Email: info@accedian.com
		
		2351 Blvd Alfred-Nobel, Suite N-410
		Saint-Laurent (Montreal), Quebec,
		H4S 2A9, Canada
		
		Phone: +1.514.331.6181 or +1.866.685.8181";
	
	description
		"This module contains the definition of an Accedian service
		session. It is session-protocol and service-endpoint data agnostic
		by design.
		
		Session protocol specific models are added through session protocol
		modules. Their implementation is contained in modules following the
		format: Accedian-session-<proto>.yang. They augment the service
		model when sessions:type match.
		
		Session endpoints are specified by refering to pre-existing endpoint IDs.
		
		Copyright (c) Accedian Networks, Inc.
		All rights reserved";
	
	revision 2022-10-25 {
		description
			"Initial revision ";
	}
	
	notification state-change-event {
		description
			"This notification is sent when the state of the session changes";
		
		leaf identifier {
			description
				"An identifier specifying on which session the state-change happened. This
				leaf will match the name of an existing session ID (i.e the value
				of /sessions/identifier)";
			type string;
		}
		
		uses acdst:service-session-state-data;
	}
	
	container sessions {
		list session {
			description
				"A list of all the configured sessions. The sessions are identified by
				a session id";
			key session-id;
			
			leaf session-id {
				type acdt:id;
				acdext:tag-metadata session-id;
				description
					"Unique identifier for the session.
					tag-metadata: This leaf will be included as part of the analytics
					metadata as { session-id : <session-id> }";
			}
			
			leaf session-name {
				type string;
				acdext:tag-metadata session-name;
				description
					"Name given to this session.
					tag-metadata: This leaf will be included as part of the analytics
					metadata as { session-name : <session-name> }";
			}
			
			leaf description {
				type string;
				description
					"A description of this sessions";
			}
			
			leaf session-type {
				type identityref {
					base acdst:session;
				}
				description
					"The type of service configured for this session";
			}
			
			list service-endpoints {
				description
					"The list of service endpoints involved in the session.";
				key endpoint-id;
				
				leaf endpoint-id {
					type leafref {
						path "/acdsep:service-endpoints/acdsep:service-endpoint/acdsep:endpoint-id";
					}
					description
						"A reference to the service endpoint unique identifier";
				}
				
				container session-protocol {
					description
						"Protocol/session-service specific configuration for this endpoint. The configuration
						is dependent on the session protocol type specified in /sessions/session/session-type.
						It is Implemented as a Yang augment mount point";
				}
			}
			
			container status {
				config false;
				uses acdst:service-session-state-data;
			}
			
			leaf auto-start {
				type boolean;
				default false;
				description
					"If set to true, the session will be started automatically when configured. If set to
					false (default), a subsequent start action is required to start the session";
			}

			action start {
        description
          "This action will start the session";
			}

			action stop {
        description
          "This action will stop the session";
			}
		}
	}
}
